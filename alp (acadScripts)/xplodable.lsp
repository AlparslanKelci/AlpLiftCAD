;;;				ALLOW TO EXPLOAD (ALL BLOCKS)           			;;;
(defun c:xploadable ()
(vl-load-com)
(vlax-for b (vla-get-Blocks
(vla-get-ActiveDocument (vlax-get-acad-object))
)
(or (wcmatch (vla-get-Name b) "`**_Space*")
(vla-put-explodable b :vlax-true)
)
)
(princ)
)
(c:xploadable)
